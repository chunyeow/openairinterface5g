-- **************************************************************
--
-- Constant definitions
--
-- **************************************************************

X2AP-Constants {
itu-t (0) identified-organization (4) etsi (0) mobileDomain (0) 
eps-Access (21) modules (3) x2ap (2) version1 (1) x2ap-Constants (4) }

DEFINITIONS AUTOMATIC TAGS ::= 

BEGIN

IMPORTS
	X2ap-ProcedureCode,
	X2ap-ProtocolIE-ID
FROM X2AP-CommonDataTypes;

-- **************************************************************
--
-- Elementary Procedures
--
-- **************************************************************

id-handoverPreparation											X2ap-ProcedureCode ::= 0
id-handoverCancel												X2ap-ProcedureCode ::= 1
id-loadIndication												X2ap-ProcedureCode ::= 2
id-errorIndication												X2ap-ProcedureCode ::= 3
id-snStatusTransfer												X2ap-ProcedureCode ::= 4
id-uEContextRelease												X2ap-ProcedureCode ::= 5
id-x2Setup														X2ap-ProcedureCode ::= 6
id-reset														X2ap-ProcedureCode ::= 7
id-eNBConfigurationUpdate										X2ap-ProcedureCode ::= 8
id-resourceStatusReportingInitiation							X2ap-ProcedureCode ::= 9
id-resourceStatusReporting										X2ap-ProcedureCode ::= 10
id-privateMessage												X2ap-ProcedureCode ::= 11
id-mobilitySettingsChange										X2ap-ProcedureCode ::= 12
id-rLFIndication												X2ap-ProcedureCode ::= 13
id-handoverReport												X2ap-ProcedureCode ::= 14
id-cellActivation												X2ap-ProcedureCode ::= 15



-- **************************************************************
--
-- Lists
--
-- **************************************************************

x2ap-maxEARFCN									INTEGER ::= 65535
x2ap-maxInterfaces								INTEGER ::= 16
x2ap-maxCellineNB								INTEGER ::= 256
x2ap-maxnoofBands								INTEGER ::= 16
x2ap-maxnoofBearers								INTEGER ::= 256
x2ap-maxNrOfErrors								INTEGER ::= 256
x2ap-maxnoofPDCP-SN								INTEGER ::= 16
x2ap-maxnoofEPLMNs								INTEGER ::= 15
x2ap-maxnoofEPLMNsPlusOne						INTEGER ::= 16
x2ap-maxnoofForbLACs							INTEGER ::= 4096
x2ap-maxnoofForbTACs							INTEGER ::= 4096
x2ap-maxnoofBPLMNs								INTEGER ::= 6
x2ap-maxnoofNeighbours							INTEGER ::= 512
x2ap-maxnoofPRBs								INTEGER ::= 110
x2ap-maxPools									INTEGER ::= 16
x2ap-maxnoofCells								INTEGER ::= 16
x2ap-maxnoofMBSFN								INTEGER ::= 8
x2ap-maxFailedMeasObjects						INTEGER ::= 32
x2ap-maxnoofCellIDforMDT						INTEGER ::= 32
x2ap-maxnoofTAforMDT							INTEGER ::= 8
x2ap-maxnoofMBMSServiceAreaIdentities			INTEGER ::= 256


-- **************************************************************
--
-- IEs
--
-- **************************************************************

id-E-RABs-Admitted-Item														X2ap-ProtocolIE-ID ::= 0
id-E-RABs-Admitted-List														X2ap-ProtocolIE-ID ::= 1
id-E-RAB-Item																X2ap-ProtocolIE-ID ::= 2
id-E-RABs-NotAdmitted-List													X2ap-ProtocolIE-ID ::= 3
id-E-RABs-ToBeSetup-Item													X2ap-ProtocolIE-ID ::= 4
id-Cause																	X2ap-ProtocolIE-ID ::= 5
id-CellInformation															X2ap-ProtocolIE-ID ::= 6
id-CellInformation-Item														X2ap-ProtocolIE-ID ::= 7
id-New-eNB-UE-X2AP-ID														X2ap-ProtocolIE-ID ::= 9
id-Old-eNB-UE-X2AP-ID														X2ap-ProtocolIE-ID ::= 10
id-TargetCell-ID															X2ap-ProtocolIE-ID ::= 11
id-TargeteNBtoSource-eNBTransparentContainer								X2ap-ProtocolIE-ID ::= 12
id-TraceActivation															X2ap-ProtocolIE-ID ::= 13
id-UE-ContextInformation													X2ap-ProtocolIE-ID ::= 14
id-UE-HistoryInformation													X2ap-ProtocolIE-ID ::= 15
id-UE-X2AP-ID																X2ap-ProtocolIE-ID ::= 16
id-CriticalityDiagnostics													X2ap-ProtocolIE-ID ::= 17
id-E-RABs-SubjectToStatusTransfer-List										X2ap-ProtocolIE-ID ::= 18
id-E-RABs-SubjectToStatusTransfer-Item										X2ap-ProtocolIE-ID ::= 19
id-ServedCells																X2ap-ProtocolIE-ID ::= 20
id-GlobalENB-ID																X2ap-ProtocolIE-ID ::= 21
id-TimeToWait																X2ap-ProtocolIE-ID ::= 22
id-GUMMEI-ID																X2ap-ProtocolIE-ID ::= 23
id-GUGroupIDList															X2ap-ProtocolIE-ID ::= 24
id-ServedCellsToAdd															X2ap-ProtocolIE-ID ::= 25
id-ServedCellsToModify														X2ap-ProtocolIE-ID ::= 26
id-ServedCellsToDelete														X2ap-ProtocolIE-ID ::= 27
id-Registration-Request														X2ap-ProtocolIE-ID ::= 28
id-CellToReport																X2ap-ProtocolIE-ID ::= 29
id-ReportingPeriodicity														X2ap-ProtocolIE-ID ::= 30
id-CellToReport-Item														X2ap-ProtocolIE-ID ::= 31
id-CellMeasurementResult													X2ap-ProtocolIE-ID ::= 32
id-CellMeasurementResult-Item												X2ap-ProtocolIE-ID ::= 33
id-GUGroupIDToAddList														X2ap-ProtocolIE-ID ::= 34
id-GUGroupIDToDeleteList													X2ap-ProtocolIE-ID ::= 35
id-SRVCCOperationPossible													X2ap-ProtocolIE-ID ::= 36
id-Measurement-ID															X2ap-ProtocolIE-ID ::= 37
id-ReportCharacteristics													X2ap-ProtocolIE-ID ::= 38
id-ENB1-Measurement-ID														X2ap-ProtocolIE-ID ::= 39
id-ENB2-Measurement-ID														X2ap-ProtocolIE-ID ::= 40
id-Number-of-Antennaports													X2ap-ProtocolIE-ID ::= 41
id-CompositeAvailableCapacityGroup											X2ap-ProtocolIE-ID ::= 42
id-ENB1-Cell-ID																X2ap-ProtocolIE-ID ::= 43
id-ENB2-Cell-ID																X2ap-ProtocolIE-ID ::= 44
id-ENB2-Proposed-Mobility-Parameters										X2ap-ProtocolIE-ID ::= 45
id-ENB1-Mobility-Parameters													X2ap-ProtocolIE-ID ::= 46
id-ENB2-Mobility-Parameters-Modification-Range								X2ap-ProtocolIE-ID ::= 47
id-FailureCellPCI															X2ap-ProtocolIE-ID ::= 48
id-Re-establishmentCellECGI													X2ap-ProtocolIE-ID ::= 49
id-FailureCellCRNTI															X2ap-ProtocolIE-ID ::= 50
id-ShortMAC-I																X2ap-ProtocolIE-ID ::= 51
id-SourceCellECGI															X2ap-ProtocolIE-ID ::= 52
id-FailureCellECGI															X2ap-ProtocolIE-ID ::= 53
id-HandoverReportType														X2ap-ProtocolIE-ID ::= 54
id-PRACH-Configuration														X2ap-ProtocolIE-ID ::= 55
id-MBSFN-Subframe-Info														X2ap-ProtocolIE-ID ::= 56
id-ServedCellsToActivate													X2ap-ProtocolIE-ID ::= 57
id-ActivatedCellList														X2ap-ProtocolIE-ID ::= 58
id-DeactivationIndication													X2ap-ProtocolIE-ID ::= 59
id-UE-RLF-Report-Container													X2ap-ProtocolIE-ID ::= 60
id-ABSInformation															X2ap-ProtocolIE-ID ::= 61
id-InvokeIndication															X2ap-ProtocolIE-ID ::= 62
id-ABS-Status																X2ap-ProtocolIE-ID ::= 63
id-PartialSuccessIndicator													X2ap-ProtocolIE-ID ::= 64
id-MeasurementInitiationResult-List											X2ap-ProtocolIE-ID ::= 65
id-MeasurementInitiationResult-Item											X2ap-ProtocolIE-ID ::= 66
id-MeasurementFailureCause-Item												X2ap-ProtocolIE-ID ::= 67
id-CompleteFailureCauseInformation-List										X2ap-ProtocolIE-ID ::= 68
id-CompleteFailureCauseInformation-Item										X2ap-ProtocolIE-ID ::= 69
id-CSG-Id																	X2ap-ProtocolIE-ID ::= 70
id-CSGMembershipStatus														X2ap-ProtocolIE-ID ::= 71
id-MDTConfiguration															X2ap-ProtocolIE-ID ::= 72
id-ManagementBasedMDTallowed												X2ap-ProtocolIE-ID ::= 74
id-RRCConnSetupIndicator													X2ap-ProtocolIE-ID ::= 75
id-NeighbourTAC																X2ap-ProtocolIE-ID ::= 76
id-Time-UE-StayedInCell-EnhancedGranularity									X2ap-ProtocolIE-ID ::= 77
id-RRCConnReestabIndicator													X2ap-ProtocolIE-ID ::= 78
id-MBMS-Service-Area-List													X2ap-ProtocolIE-ID ::= 79
id-HO-cause																	X2ap-ProtocolIE-ID ::= 80
id-TargetCellInUTRAN														X2ap-ProtocolIE-ID ::= 81
id-MultibandInfoList														X2ap-ProtocolIE-ID ::= 84

END
