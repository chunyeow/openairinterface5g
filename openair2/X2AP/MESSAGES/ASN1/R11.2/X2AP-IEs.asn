-- **************************************************************
--
-- Information Element Definitions
--
-- **************************************************************

X2AP-IEs {
itu-t (0) identified-organization (4) etsi (0) mobileDomain (0) 
eps-Access (21) modules (3) x2ap (2) version1 (1) x2ap-IEs (2) }

DEFINITIONS AUTOMATIC TAGS ::= 

BEGIN

IMPORTS
	id-E-RAB-Item,
	id-Number-of-Antennaports,
	id-MBSFN-Subframe-Info,
	id-PRACH-Configuration,
	id-CSG-Id,
	id-MDTConfiguration,
	id-MultibandInfoList,
	id-NeighbourTAC,
	id-Time-UE-StayedInCell-EnhancedGranularity,
	id-MBMS-Service-Area-List,
	id-HO-cause,
	x2ap-maxnoofBearers,
	x2ap-maxCellineNB,
	x2ap-maxEARFCN,
	x2ap-maxInterfaces,
	x2ap-maxnoofBands,
	x2ap-maxnoofBPLMNs,
	x2ap-maxnoofCells,
	x2ap-maxnoofEPLMNs,
	x2ap-maxnoofEPLMNsPlusOne,
	x2ap-maxnoofForbLACs,
	x2ap-maxnoofForbTACs,
	x2ap-maxnoofNeighbours,
	x2ap-maxnoofPRBs,
	x2ap-maxNrOfErrors,
	x2ap-maxPools,
	x2ap-maxnoofMBSFN,
	x2ap-maxnoofTAforMDT,
	x2ap-maxnoofCellIDforMDT,
	x2ap-maxnoofMBMSServiceAreaIdentities
FROM X2AP-Constants

	x2ap-maxProtocolExtensions,
	X2ap-Criticality,
	X2ap-ProcedureCode,
	X2ap-ProtocolIE-ID,
	X2ap-TriggeringMessage
FROM X2AP-CommonDataTypes

--	ProtocolExtensionContainer{},
--	ProtocolIE-Single-Container{},
--	X2AP-PROTOCOL-EXTENSION,
--	X2AP-PROTOCOL-IES		
--FROM X2AP-Containers

	X2ap-IE
FROM X2AP-PDU;

--EURECOM ADD
X2ap-IE-Extensions ::= SEQUENCE (SIZE (1..x2ap-maxProtocolExtensions)) OF X2ap-IE

-- A

X2ap-ABSInformation ::= CHOICE {
	fdd					X2ap-ABSInformationFDD,
	tdd					X2ap-ABSInformationTDD,
	abs-inactive		NULL,
	...
}

X2ap-ABSInformationFDD ::= SEQUENCE {
	abs-pattern-info					BIT STRING (SIZE(40)),
	numberOfCellSpecificAntennaPorts	ENUMERATED {one, two, four, ...},
	measurement-subset					BIT STRING (SIZE(40)),
-- iE-Extensions						ProtocolExtensionContainer { { X2ap-ABSInformationFDD-ExtIEs} } OPTIONAL,
	iE-Extensions               X2ap-IE-Extensions OPTIONAL,
    	...
}

X2ap-ABSInformationFDD-ExtIEs X2AP-PROTOCOL-EXTENSION ::= {
	...
}

X2ap-ABSInformationTDD ::= SEQUENCE {
	abs-pattern-info					BIT STRING (SIZE(1..70, ...)),
--EURECOM COMMENT	numberOfCellSpecificAntennaPorts	ENUMERATED {one, two, four, ...},
	numberOfCellSpecificAntennaPortsTDD	ENUMERATED {one, two, four, ...},
	measurement-subset					BIT STRING (SIZE(1..70, ...)),
--EURECOM COMMENT, ADDED NEXT LINE 	iE-Extensions						ProtocolExtensionContainer { { X2ap-ABSInformationTDD-ExtIEs} } OPTIONAL,
	iE-Extensions               X2ap-IE-Extensions OPTIONAL,
	...
}

X2ap-ABSInformationTDD-ExtIEs X2AP-PROTOCOL-EXTENSION ::= {
	...
}

X2ap-ABS-Status ::= SEQUENCE {
	dL-ABS-status								X2ap-DL-ABS-status,
	usableABSInformation						X2ap-UsableABSInformation,
--EURECOM COMMENT, ADDED NEXT LINE 	iE-Extensions								ProtocolExtensionContainer { {X2ap-ABS-Status-ExtIEs} } OPTIONAL,
	iE-Extensions               X2ap-IE-Extensions OPTIONAL,
	...
}

X2ap-ABS-Status-ExtIEs X2AP-PROTOCOL-EXTENSION ::= {
	...
}

X2ap-DL-ABS-status::= INTEGER (0..100)

X2ap-AS-SecurityInformation ::= SEQUENCE {
	key-eNodeB-star		X2ap-Key-eNodeB-Star,
	nextHopChainingCount			X2ap-NextHopChainingCount,
--EURECOM COMMENT, ADDED NEXT LINE 	iE-Extensions						ProtocolExtensionContainer { { X2ap-AS-SecurityInformation-ExtIEs} } OPTIONAL,
	iE-Extensions               X2ap-IE-Extensions OPTIONAL,
	...
}

X2ap-AS-SecurityInformation-ExtIEs X2AP-PROTOCOL-EXTENSION ::= {
	...
}


X2ap-AllocationAndRetentionPriority ::= SEQUENCE {
	priorityLevel				X2ap-PriorityLevel,
	pre-emptionCapability		X2ap-Pre-emptionCapability,
	pre-emptionVulnerability	X2ap-Pre-emptionVulnerability,
--EURECOM COMMENT, ADDED NEXT LINE 	iE-Extensions				ProtocolExtensionContainer { {X2ap-AllocationAndRetentionPriority-ExtIEs} } OPTIONAL,
	iE-Extensions               X2ap-IE-Extensions OPTIONAL,
	...
}

X2ap-AllocationAndRetentionPriority-ExtIEs X2AP-PROTOCOL-EXTENSION ::= {
	...
}

X2ap-AreaScopeOfMDT ::= CHOICE {	
	cellBased					X2ap-CellBasedMDT,
	tABased						X2ap-TABasedMDT,
	pLMNWide					NULL,
	...
}

-- B


X2ap-BitRate ::= INTEGER (0..10000000000)
X2ap-BroadcastPLMNs-Item ::= SEQUENCE (SIZE(1..x2ap-maxnoofBPLMNs)) OF X2ap-PLMN-Identity


-- C

X2ap-CapacityValue ::= INTEGER (0..100)

X2ap-CellCapacityClassValue ::= INTEGER (1..100, ...)

X2ap-Cause ::= CHOICE {
	radioNetwork		X2ap-CauseRadioNetwork,
	transport			X2ap-CauseTransport,
	protocol			X2ap-CauseProtocol,
	misc				X2ap-CauseMisc,
	...
}

X2ap-CauseMisc ::= ENUMERATED {
	control-processing-overload,
	hardware-failure,
	om-intervention,
	not-enough-user-plane-processing-resources,
	unspecified,
	...
}

X2ap-CauseProtocol ::= ENUMERATED {
	transfer-syntax-error,
	abstract-syntax-error-reject,
	abstract-syntax-error-ignore-and-notify,
	message-not-compatible-with-receiver-state,
	semantic-error,
	unspecified,
	abstract-syntax-error-falsely-constructed-message,
	...
}

X2ap-CauseRadioNetwork ::= ENUMERATED {
	handover-desirable-for-radio-reasons,
	time-critical-handover,
	resource-optimisation-handover,
	reduce-load-in-serving-cell,
	partial-handover,
	unknown-new-eNB-UE-X2AP-ID, 
	unknown-old-eNB-UE-X2AP-ID, 
	unknown-pair-of-UE-X2AP-ID,
	ho-target-not-allowed,
	tx2relocoverall-expiry,
	trelocprep-expiry,
	cell-not-available,
	no-radio-resources-available-in-target-cell,
	invalid-MME-GroupID,
	unknown-MME-Code,
	encryption-and-or-integrity-protection-algorithms-not-supported,
	reportCharacteristicsEmpty,
	noReportPeriodicity,
	existingMeasurementID,
	unknown-eNB-Measurement-ID,
	measurement-temporarily-not-available,
	unspecified,
	...,
	load-balancing,
	handover-optimisation,
	value-out-of-allowed-range,
	multiple-E-RAB-ID-instances,
	switch-off-ongoing,
	not-supported-QCI-value,
	measurement-not-supported-for-the-object

}

X2ap-CauseTransport ::= ENUMERATED {
	transport-resource-unavailable,
	unspecified,
	...
}

X2ap-CellBasedMDT::= SEQUENCE {
	cellIdListforMDT	X2ap-CellIdListforMDT,
--EURECOM COMMENT, ADDED NEXT LINE 	iE-Extensions		ProtocolExtensionContainer { {X2ap-CellBasedMDT-ExtIEs} } OPTIONAL,
	iE-Extensions               X2ap-IE-Extensions OPTIONAL,
	...
}

X2ap-CellBasedMDT-ExtIEs X2AP-PROTOCOL-EXTENSION ::= {
	...
}

X2ap-CellIdListforMDT ::= SEQUENCE (SIZE(1..x2ap-maxnoofCellIDforMDT)) OF X2ap-ECGI

X2ap-Cell-Size ::= ENUMERATED {verysmall, small, medium, large, ... }


X2ap-CellType ::= SEQUENCE {
	cell-Size						X2ap-Cell-Size,
--EURECOM COMMENT, ADDED NEXT LINE 	iE-Extensions					ProtocolExtensionContainer { { X2ap-CellType-ExtIEs}}	OPTIONAL,
	iE-Extensions               X2ap-IE-Extensions OPTIONAL,
	...
}

X2ap-CellType-ExtIEs X2AP-PROTOCOL-EXTENSION ::= {
	...
}

X2ap-CompositeAvailableCapacityGroup	::= SEQUENCE {
	dL-CompositeAvailableCapacity					X2ap-CompositeAvailableCapacity,
	uL-CompositeAvailableCapacity					X2ap-CompositeAvailableCapacity,
--EURECOM COMMENT, ADDED NEXT LINE 	iE-Extensions									ProtocolExtensionContainer { { X2ap-CompositeAvailableCapacityGroup-ExtIEs} } OPTIONAL,
	iE-Extensions               X2ap-IE-Extensions OPTIONAL,
	...
}

X2ap-CompositeAvailableCapacityGroup-ExtIEs X2AP-PROTOCOL-EXTENSION ::= {
	...
}

X2ap-CompositeAvailableCapacity ::= SEQUENCE {
	cellCapacityClassValue							X2ap-CellCapacityClassValue				OPTIONAL,
	capacityValue									X2ap-CapacityValue,
--EURECOM COMMENT, ADDED NEXT LINE 	iE-Extensions									ProtocolExtensionContainer { { X2ap-CompositeAvailableCapacity-ExtIEs} } OPTIONAL,
	iE-Extensions               X2ap-IE-Extensions OPTIONAL,
	...
}

X2ap-CompositeAvailableCapacity-ExtIEs X2AP-PROTOCOL-EXTENSION ::= {
	...
}

X2ap-COUNTvalue ::= SEQUENCE {
	pDCP-SN					X2ap-PDCP-SN,
	hFN						X2ap-HFN,
--EURECOM COMMENT, ADDED NEXT LINE 	iE-Extensions			ProtocolExtensionContainer { { X2ap-COUNTvalue-ExtIEs} } OPTIONAL,
	iE-Extensions               X2ap-IE-Extensions OPTIONAL,
	...
}

X2ap-COUNTvalue-ExtIEs X2AP-PROTOCOL-EXTENSION ::= {
	...
}


X2ap-CriticalityDiagnostics ::= SEQUENCE {
	procedureCode					X2ap-ProcedureCode					OPTIONAL,
	triggeringMessage				X2ap-TriggeringMessage				OPTIONAL,
	procedureCriticality			X2ap-Criticality						OPTIONAL,
	iEsCriticalityDiagnostics		X2ap-CriticalityDiagnostics-IE-List	OPTIONAL,
--EURECOM COMMENT, ADDED NEXT LINE 	iE-Extensions					ProtocolExtensionContainer { {X2ap-CriticalityDiagnostics-ExtIEs} }	OPTIONAL,
	iE-Extensions               X2ap-IE-Extensions OPTIONAL,
	...
}


X2ap-CriticalityDiagnostics-ExtIEs X2AP-PROTOCOL-EXTENSION ::= {
	...
}

X2ap-CriticalityDiagnostics-IE-List ::= SEQUENCE (SIZE (1..x2ap-maxNrOfErrors)) OF
	SEQUENCE {
		iECriticality			X2ap-Criticality,
		iE-ID					X2ap-ProtocolIE-ID,
		typeOfError				X2ap-TypeOfError,
	--EURECOM COMMENT, ADDED NEXT LINE 	iE-Extensions			ProtocolExtensionContainer { {X2ap-CriticalityDiagnostics-IE-List-ExtIEs} } OPTIONAL,
	iE-Extensions               X2ap-IE-Extensions OPTIONAL,
		...
}

X2ap-CriticalityDiagnostics-IE-List-ExtIEs X2AP-PROTOCOL-EXTENSION ::= {
	...
}

X2ap-CRNTI ::= BIT STRING (SIZE (16))

X2ap-CSGMembershipStatus ::= ENUMERATED { 
	member,
	not-member
}

X2ap-CSG-Id ::= BIT STRING (SIZE (27))

X2ap-CyclicPrefixDL ::= ENUMERATED { 
	normal,
	extended,
	...
}

X2ap-CyclicPrefixUL ::= ENUMERATED { 
	normal,
	extended,
	...
}


-- D

X2ap-DeactivationIndication::= ENUMERATED { 
	deactivated,
	...
}

X2ap-DL-Forwarding ::= ENUMERATED {
	dL-forwardingProposed,
	...
}

X2ap-DL-GBR-PRB-usage::= INTEGER (0..100)

X2ap-DL-non-GBR-PRB-usage::= INTEGER (0..100)

X2ap-DL-Total-PRB-usage::= INTEGER (0..100)

-- E

X2ap-EARFCN ::= INTEGER (0..x2ap-maxEARFCN)

X2ap-FDD-Info ::= SEQUENCE {
	uL-EARFCN						X2ap-EARFCN,
	dL-EARFCN						X2ap-EARFCN,
	uL-Transmission-Bandwidth		X2ap-Transmission-Bandwidth,
	dL-Transmission-Bandwidth		X2ap-Transmission-Bandwidth,
--EURECOM COMMENT, ADDED NEXT LINE 	iE-Extensions				ProtocolExtensionContainer { {X2ap-FDD-Info-ExtIEs} } OPTIONAL,
	iE-Extensions               X2ap-IE-Extensions OPTIONAL,
	...
}

X2ap-FDD-Info-ExtIEs X2AP-PROTOCOL-EXTENSION ::= {
	...
}

X2ap-TDD-Info ::= SEQUENCE {
	eARFCN							X2ap-EARFCN,
	transmission-Bandwidth			X2ap-Transmission-Bandwidth,
	subframeAssignment				X2ap-SubframeAssignment,
	specialSubframe-Info				X2ap-SpecialSubframe-Info,
--EURECOM COMMENT, ADDED NEXT LINE 	iE-Extensions				ProtocolExtensionContainer { {X2ap-TDD-Info-ExtIEs} } OPTIONAL,
	iE-Extensions               X2ap-IE-Extensions OPTIONAL,
	...
}
X2ap-TDD-Info-ExtIEs X2AP-PROTOCOL-EXTENSION ::= {
	...
}

X2ap-EUTRA-Mode-Info ::= CHOICE {
	fDD		X2ap-FDD-Info,
	tDD		X2ap-TDD-Info,
	...
}

X2ap-ECGI ::= SEQUENCE {
	pLMN-Identity				X2ap-PLMN-Identity,
	eUTRANcellIdentifier		X2ap-EUTRANCellIdentifier,
--EURECOM COMMENT, ADDED NEXT LINE 	iE-Extensions				ProtocolExtensionContainer { {X2ap-ECGI-ExtIEs} } OPTIONAL,
	iE-Extensions               X2ap-IE-Extensions OPTIONAL,
	...
}

X2ap-ECGI-ExtIEs X2AP-PROTOCOL-EXTENSION ::= {
	...
}

X2ap-ENB-ID ::= CHOICE {
	macro-eNB-ID	BIT STRING (SIZE (20)),
	home-eNB-ID		BIT STRING (SIZE (28)),
	...
}

X2ap-EncryptionAlgorithms ::= BIT STRING (SIZE (16, ...))

X2ap-EPLMNs ::= SEQUENCE (SIZE(1..x2ap-maxnoofEPLMNs)) OF X2ap-PLMN-Identity

X2ap-E-RAB-ID ::= INTEGER (0..15, ...)  

X2ap-E-RAB-Level-QoS-Parameters ::= SEQUENCE {
	qCI								X2ap-QCI,
	allocationAndRetentionPriority	X2ap-AllocationAndRetentionPriority,
	gbrQosInformation				X2ap-GBR-QosInformation													OPTIONAL,
--EURECOM COMMENT, ADDED NEXT LINE 	iE-Extensions					ProtocolExtensionContainer { { X2ap-E-RAB-Level-QoS-Parameters-ExtIEs} }	OPTIONAL,
	iE-Extensions               X2ap-IE-Extensions OPTIONAL,
	...
}

X2ap-E-RAB-Level-QoS-Parameters-ExtIEs X2AP-PROTOCOL-EXTENSION ::= {
	...
}

--EURECOM X2ap-E-RAB-List ::= SEQUENCE (SIZE(1.. x2ap-maxnoofBearers)) OF ProtocolIE-Single-Container { {X2ap-E-RAB-ItemIEs} }
X2ap-E-RAB-List	::= SEQUENCE (SIZE (1.. x2ap-maxnoofBearers)) OF X2ap-IE

--EURECOMX2ap-E-RAB-ItemIEs 	X2AP-PROTOCOL-IES ::= {
--EURECOM	{ ID id-E-RAB-Item	 CRITICALITY ignore 	TYPE X2ap-E-RAB-Item 	PRESENCE mandatory },
--EURECOM	...
--EURECOM}

X2ap-E-RAB-Item ::= SEQUENCE {
	e-RAB-ID				X2ap-E-RAB-ID,
	cause						X2ap-Cause,
--EURECOM COMMENT, ADDED NEXT LINE 	iE-Extensions				ProtocolExtensionContainer { {X2ap-E-RAB-Item-ExtIEs} } OPTIONAL,
	iE-Extensions               X2ap-IE-Extensions OPTIONAL,
	...
}

X2ap-E-RAB-Item-ExtIEs X2AP-PROTOCOL-EXTENSION ::= {
	...
}

X2ap-EUTRANCellIdentifier ::= BIT STRING (SIZE (28))

X2ap-EUTRANTraceID		::= OCTET STRING (SIZE (8))


X2ap-EventType ::= ENUMERATED{
	change-of-serving-cell,
	...
}


-- F

X2ap-ForbiddenInterRATs ::= ENUMERATED {
	all,
	geran,
	utran,
	cdma2000,
	...,
	geranandutran,
	cdma2000andutran

}

X2ap-ForbiddenTAs ::= SEQUENCE (SIZE(1.. x2ap-maxnoofEPLMNsPlusOne)) OF X2ap-ForbiddenTAs-Item

X2ap-ForbiddenTAs-Item ::= SEQUENCE {
	pLMN-Identity		X2ap-PLMN-Identity,
	forbiddenTACs		X2ap-ForbiddenTACs,
--EURECOM COMMENT, ADDED NEXT LINE 	iE-Extensions		ProtocolExtensionContainer { {X2ap-ForbiddenTAs-Item-ExtIEs} } OPTIONAL,
	iE-Extensions               X2ap-IE-Extensions OPTIONAL,
	...
}

X2ap-ForbiddenTAs-Item-ExtIEs X2AP-PROTOCOL-EXTENSION ::= {
	...
}

X2ap-ForbiddenTACs ::= SEQUENCE (SIZE(1..x2ap-maxnoofForbTACs)) OF X2ap-TAC

X2ap-ForbiddenLAs ::= SEQUENCE (SIZE(1..x2ap-maxnoofEPLMNsPlusOne)) OF X2ap-ForbiddenLAs-Item

X2ap-ForbiddenLAs-Item ::= SEQUENCE {	
	pLMN-Identity		X2ap-PLMN-Identity,
	forbiddenLACs		X2ap-ForbiddenLACs,
--EURECOM COMMENT, ADDED NEXT LINE 	iE-Extensions		ProtocolExtensionContainer { {X2ap-ForbiddenLAs-Item-ExtIEs} } OPTIONAL,
	iE-Extensions               X2ap-IE-Extensions OPTIONAL,
	...
}

X2ap-ForbiddenLAs-Item-ExtIEs X2AP-PROTOCOL-EXTENSION ::= {
	...
}

X2ap-ForbiddenLACs ::= SEQUENCE (SIZE(1..x2ap-maxnoofForbLACs)) OF X2ap-LAC

X2ap-Fourframes ::= BIT STRING (SIZE (24))

X2ap-FreqBandIndicator ::= INTEGER (1..64)

-- G

X2ap-GBR-QosInformation ::= SEQUENCE {
	e-RAB-MaximumBitrateDL			X2ap-BitRate,
	e-RAB-MaximumBitrateUL			X2ap-BitRate,
	e-RAB-GuaranteedBitrateDL		X2ap-BitRate,
	e-RAB-GuaranteedBitrateUL		X2ap-BitRate,
--EURECOM COMMENT, ADDED NEXT LINE 	iE-Extensions					ProtocolExtensionContainer { { X2ap-GBR-QosInformation-ExtIEs} } OPTIONAL,
	iE-Extensions               X2ap-IE-Extensions OPTIONAL,
	...
}

X2ap-GBR-QosInformation-ExtIEs X2AP-PROTOCOL-EXTENSION ::= {
	...
}

X2ap-GlobalENB-ID ::= SEQUENCE {
	pLMN-Identity			X2ap-PLMN-Identity,
	eNB-ID					X2ap-ENB-ID,
--EURECOM COMMENT, ADDED NEXT LINE 	iE-Extensions			ProtocolExtensionContainer { {X2ap-GlobalENB-ID-ExtIEs} } OPTIONAL,
	iE-Extensions               X2ap-IE-Extensions OPTIONAL,
	...
}

X2ap-GlobalENB-ID-ExtIEs X2AP-PROTOCOL-EXTENSION ::= {
	...
}

X2ap-GTPtunnelEndpoint ::= SEQUENCE {
	transportLayerAddress			X2ap-TransportLayerAddress,
	gTP-TEID						X2ap-GTP-TEI,
--EURECOM COMMENT, ADDED NEXT LINE 	iE-Extensions					ProtocolExtensionContainer { {X2ap-GTPtunnelEndpoint-ExtIEs} } OPTIONAL,
	iE-Extensions               X2ap-IE-Extensions OPTIONAL,
	...
}

X2ap-GTPtunnelEndpoint-ExtIEs X2AP-PROTOCOL-EXTENSION ::= {
	...
}

X2ap-GTP-TEI					::= OCTET STRING (SIZE (4))

X2ap-GUGroupIDList		::= SEQUENCE (SIZE (1..x2ap-maxPools)) OF X2ap-GU-Group-ID


X2ap-GU-Group-ID			::= SEQUENCE {
	pLMN-Identity		X2ap-PLMN-Identity,
	mME-Group-ID		X2ap-MME-Group-ID,
--EURECOM COMMENT, ADDED NEXT LINE 	iE-Extensions		ProtocolExtensionContainer { {X2ap-GU-Group-ID-ExtIEs} } OPTIONAL,
	iE-Extensions               X2ap-IE-Extensions OPTIONAL,
	...
}

X2ap-GU-Group-ID-ExtIEs X2AP-PROTOCOL-EXTENSION ::= {
	...
}


X2ap-GUMMEI			::= SEQUENCE {
	
	gU-Group-ID		X2ap-GU-Group-ID,
	mME-Code			X2ap-MME-Code,
--EURECOM COMMENT, ADDED NEXT LINE 	iE-Extensions					ProtocolExtensionContainer { {X2ap-GUMMEI-ExtIEs} } OPTIONAL,
	iE-Extensions               X2ap-IE-Extensions OPTIONAL,
	...
}

X2ap-GUMMEI-ExtIEs X2AP-PROTOCOL-EXTENSION ::= {
	...
}



-- H

X2ap-HandoverReportType  ::= ENUMERATED {
	hoTooEarly,
	hoToWrongCell,
	...,
	interRATpingpong
}

X2ap-HandoverRestrictionList ::= SEQUENCE {
	servingPLMN					X2ap-PLMN-Identity,
	equivalentPLMNs				X2ap-EPLMNs					OPTIONAL,
	forbiddenTAs				X2ap-ForbiddenTAs			OPTIONAL,
	forbiddenLAs				X2ap-ForbiddenLAs			OPTIONAL,
	forbiddenInterRATs			X2ap-ForbiddenInterRATs		OPTIONAL,
--EURECOM COMMENT, ADDED NEXT LINE 	iE-Extensions				ProtocolExtensionContainer { {HandoverRestrictionList-ExtIEs} }	OPTIONAL,
	iE-Extensions               X2ap-IE-Extensions OPTIONAL,
	...
}

X2ap-HandoverRestrictionList-ExtIEs X2AP-PROTOCOL-EXTENSION ::= {
	...
}

X2ap-HFN ::= INTEGER (0..1048575)

X2ap-HWLoadIndicator ::= SEQUENCE {
	dLHWLoadIndicator			X2ap-LoadIndicator,
	uLHWLoadIndicator			X2ap-LoadIndicator,
--EURECOM COMMENT, ADDED NEXT LINE 	iE-Extensions				ProtocolExtensionContainer { { X2ap-HWLoadIndicator-ExtIEs} } OPTIONAL,
	iE-Extensions               X2ap-IE-Extensions OPTIONAL,
	...
}

X2ap-HWLoadIndicator-ExtIEs X2AP-PROTOCOL-EXTENSION ::= {
	...
}


-- I

X2ap-InvokeIndication ::= ENUMERATED{
	abs-information,
	...
}

X2ap-IntegrityProtectionAlgorithms ::= BIT STRING (SIZE (16, ...))

X2ap-InterfacesToTrace ::= BIT STRING (SIZE (8)) 
-- J
-- K


X2ap-Key-eNodeB-Star  ::= BIT STRING (SIZE(256))

-- L


X2ap-LAC					::= OCTET STRING (SIZE (2)) --(EXCEPT ('0000'H|'FFFE'H))

X2ap-LastVisitedCell-Item ::= CHOICE {
	e-UTRAN-Cell					X2ap-LastVisitedEUTRANCellInformation,
	uTRAN-Cell						X2ap-LastVisitedUTRANCellInformation,
	gERAN-Cell						X2ap-LastVisitedGERANCellInformation,
	...
}

X2ap-LastVisitedEUTRANCellInformation ::= SEQUENCE {
	global-Cell-ID					X2ap-ECGI,
	cellType						X2ap-CellType,
	time-UE-StayedInCell			X2ap-Time-UE-StayedInCell,
--EURECOM COMMENT, ADDED NEXT LINE 	iE-Extensions					ProtocolExtensionContainer { { LastVisitedEUTRANCellInformation-ExtIEs} } OPTIONAL,
	iE-Extensions               X2ap-IE-Extensions OPTIONAL,
	...
}

X2ap-LastVisitedEUTRANCellInformation-ExtIEs X2AP-PROTOCOL-EXTENSION ::= {
-- Extension for Rel-11 to support enhanced granularity for time UE stayed in cell --
--EURECOM	{ ID id-Time-UE-StayedInCell-EnhancedGranularity	CRITICALITY ignore	EXTENSION X2ap-Time-UE-StayedInCell-EnhancedGranularity	PRESENCE optional}|
--EURECOM	{ ID id-HO-cause									CRITICALITY ignore	EXTENSION X2ap-Cause							PRESENCE optional},
	...
}

X2ap-LastVisitedUTRANCellInformation	::= OCTET STRING

X2ap-LastVisitedGERANCellInformation ::= CHOICE {
	undefined						NULL,
	...
}


X2ap-LoadIndicator ::= ENUMERATED {
	lowLoad,
	mediumLoad, 
	highLoad,
	overLoad,
	...
}



X2ap-LocationReportingInformation ::= SEQUENCE {
	eventType		X2ap-EventType,
	reportArea		X2ap-ReportArea,
--EURECOM COMMENT, ADDED NEXT LINE 	iE-Extensions		ProtocolExtensionContainer { {LocationReportingInformation-ExtIEs} } OPTIONAL,
	iE-Extensions               X2ap-IE-Extensions OPTIONAL,
	...
}

X2ap-LocationReportingInformation-ExtIEs X2AP-PROTOCOL-EXTENSION ::={
	...
}

-- M

X2ap-MDT-Activation		::= ENUMERATED { 
	immediate-MDT-only,
	immediate-MDT-and-Trace,
	...
}

X2ap-MDT-Configuration ::= SEQUENCE {
	mdt-Activation				X2ap-MDT-Activation,
	areaScopeOfMDT				X2ap-AreaScopeOfMDT,
	measurementsToActivate		X2ap-MeasurementsToActivate,
	reportingTriggerMDT			X2ap-ReportingTriggerMDT,
	thresholdeventA2			X2ap-ThresholdEventA2			OPTIONAL,
-- Included in case of event-triggered reporting for measurement M1
	periodicReportingMDT		X2ap-PeriodicReportingMDT		OPTIONAL,
-- Included in case of periodic reporting
--EURECOM COMMENT, ADDED NEXT LINE 	iE-Extensions				ProtocolExtensionContainer { { MDT-Configuration-ExtIEs} } OPTIONAL,
	iE-Extensions               X2ap-IE-Extensions OPTIONAL,
	...
}

X2ap-MDT-Configuration-ExtIEs X2AP-PROTOCOL-EXTENSION ::= {
	...
}

X2ap-MeasurementsToActivate::= BIT STRING (SIZE (8))

X2ap-MeasurementThresholdA2 ::= CHOICE { 
	threshold-RSRP				X2ap-Threshold-RSRP,
	threshold-RSRQ				X2ap-Threshold-RSRQ,
	...
}

X2ap-MME-Group-ID	::= OCTET STRING (SIZE (2))

X2ap-MME-Code		::= OCTET STRING (SIZE (1))

X2ap-Measurement-ID	::= INTEGER (1..4095, ...) 

X2ap-MBMS-Service-Area-Identity-List ::= SEQUENCE (SIZE(1.. x2ap-maxnoofMBMSServiceAreaIdentities)) OF X2ap-MBMS-Service-Area-Identity

X2ap-MBMS-Service-Area-Identity ::= OCTET STRING (SIZE (2))

X2ap-MBSFN-Subframe-Infolist::= SEQUENCE (SIZE(1.. x2ap-maxnoofMBSFN)) OF X2ap-MBSFN-Subframe-Info

X2ap-MBSFN-Subframe-Info	::= SEQUENCE {
	radioframeAllocationPeriod		X2ap-RadioframeAllocationPeriod,
	radioframeAllocationOffset		X2ap-RadioframeAllocationOffset,
	subframeAllocation				X2ap-SubframeAllocation,
--EURECOM COMMENT, ADDED NEXT LINE 	iE-Extensions			ProtocolExtensionContainer { { MBSFN-Subframe-Info-ExtIEs } } 	OPTIONAL,
	iE-Extensions               X2ap-IE-Extensions OPTIONAL,
	...
}

X2ap-MBSFN-Subframe-Info-ExtIEs X2AP-PROTOCOL-EXTENSION ::= {
	...
}

X2ap-ManagementBasedMDTallowed ::= ENUMERATED {allowed, ...}

X2ap-MobilityParametersModificationRange ::= SEQUENCE {
	handoverTriggerChangeLowerLimit		INTEGER (-20..20),
	handoverTriggerChangeUpperLimit		INTEGER (-20..20),
	...
}

X2ap-MobilityParametersInformation ::= SEQUENCE {
	handoverTriggerChange			INTEGER (-20..20),
	...
}

X2ap-MultibandInfoList ::= SEQUENCE (SIZE(1..x2ap-maxnoofBands)) OF X2ap-BandInfo 


X2ap-BandInfo	::= SEQUENCE {
	freqBandIndicator		X2ap-FreqBandIndicator,
--EURECOM COMMENT, ADDED NEXT LINE 	iE-Extensions			ProtocolExtensionContainer { { BandInfo-ExtIEs } } 	OPTIONAL,
	iE-Extensions               X2ap-IE-Extensions OPTIONAL,
	...
}

X2ap-BandInfo-ExtIEs X2AP-PROTOCOL-EXTENSION ::= {
	...
}

-- N

X2ap-Neighbour-Information ::= SEQUENCE (SIZE (0..x2ap-maxnoofNeighbours)) OF X2ap-Neighbour-Information-Elm

X2ap-Neighbour-Information-Elm ::= SEQUENCE {
	eCGI						X2ap-ECGI,
	pCI					 	X2ap-PCI,
	eARFCN						X2ap-EARFCN,
--EURECOM COMMENT, ADDED NEXT LINE 	iE-Extensions		 ProtocolExtensionContainer { {X2ap-Neighbour-Information-ExtIEs} } OPTIONAL,
	iE-Extensions               X2ap-IE-Extensions OPTIONAL,
	...
}

X2ap-Neighbour-Information-ExtIEs X2AP-PROTOCOL-EXTENSION ::= {
--LG	{ ID id-NeighbourTAC		CRITICALITY ignore		EXTENSION TAC		PRESENCE optional},
	...
}

X2ap-NextHopChainingCount ::= INTEGER (0..7)

X2ap-Number-of-Antennaports ::= ENUMERATED {
		an1,
	 	an2,
		an4,
		...
}

-- O

X2ap-Oneframe ::= BIT STRING (SIZE (6))

-- P

X2ap-PDCP-SN ::= INTEGER (0..4095)  

X2ap-PCI ::= INTEGER (0..503, ...)

X2ap-PeriodicReportingMDT ::= SEQUENCE { 
	reportInterval				X2ap-ReportIntervalMDT,
	reportAmount				X2ap-ReportAmountMDT,
--EURECOM COMMENT, ADDED NEXT LINE 	iE-Extensions				ProtocolExtensionContainer { { PeriodicReportingMDT-ExtIEs} } OPTIONAL,
	iE-Extensions               X2ap-IE-Extensions OPTIONAL,
	...
}

X2ap-PeriodicReportingMDT-ExtIEs X2AP-PROTOCOL-EXTENSION ::= {
	...
}

X2ap-PLMN-Identity ::= OCTET STRING (SIZE(3))

X2ap-PRACH-Configuration  ::= SEQUENCE {
	rootSequenceIndex						INTEGER (0..837),
	zeroCorrelationIndex					INTEGER (0..15),
	highSpeedFlag							BOOLEAN,
	prach-FreqOffset						INTEGER (0..94),
	prach-ConfigIndex						INTEGER (0..63)        OPTIONAL,  -- present for TDD --
--EURECOM COMMENT, ADDED NEXT LINE 	iE-Extensions							ProtocolExtensionContainer { {PRACH-Configuration-ExtIEs} }	OPTIONAL,
	iE-Extensions               X2ap-IE-Extensions OPTIONAL,
	...
}

X2ap-PRACH-Configuration-ExtIEs X2AP-PROTOCOL-EXTENSION ::= {
	...
}

X2ap-Pre-emptionCapability ::= ENUMERATED {
	shall-not-trigger-pre-emption,
	may-trigger-pre-emption
}

X2ap-Pre-emptionVulnerability ::= ENUMERATED {
	not-pre-emptable,
	pre-emptable
}

X2ap-PriorityLevel				::= INTEGER { spare (0), highest (1), lowest (14), no-priority (15) } (0..15)

-- Q

X2ap-QCI ::= INTEGER (0..255)

-- R

X2ap-RadioframeAllocationOffset ::= INTEGER (0..7, ...)

X2ap-RadioframeAllocationPeriod ::= ENUMERATED{
	n1,
	n2,
	n4,
	n8,
	n16,
	n32,
	...
}


X2ap-RadioResourceStatus	::= SEQUENCE {
	dL-GBR-PRB-usage							X2ap-DL-GBR-PRB-usage,
	uL-GBR-PRB-usage							X2ap-UL-GBR-PRB-usage,
	dL-non-GBR-PRB-usage						X2ap-DL-non-GBR-PRB-usage,
	uL-non-GBR-PRB-usage						X2ap-UL-non-GBR-PRB-usage,
	dL-Total-PRB-usage							X2ap-DL-Total-PRB-usage,
	uL-Total-PRB-usage							X2ap-UL-Total-PRB-usage,
--EURECOM COMMENT, ADDED NEXT LINE 	iE-Extensions								ProtocolExtensionContainer { {RadioResourceStatus-ExtIEs} } OPTIONAL,
	iE-Extensions               X2ap-IE-Extensions OPTIONAL,
	...
}

X2ap-RadioResourceStatus-ExtIEs X2AP-PROTOCOL-EXTENSION ::= {
	...
}

X2ap-ReceiveStatusofULPDCPSDUs ::= BIT STRING (SIZE(4096))

X2ap-Registration-Request	::= ENUMERATED {
	start,
	stop,
	...
}
 
X2ap-RelativeNarrowbandTxPower ::= SEQUENCE {

	rNTP-PerPRB							BIT STRING (SIZE(6..110, ...)),
	rNTP-Threshold						X2ap-RNTP-Threshold,
--EURECOM COMMENT	numberOfCellSpecificAntennaPorts	ENUMERATED {one, two, four, ...},
	numberOfCellSpecificAntennaPortsTxPower	ENUMERATED {one, two, four, ...},
	p-B									INTEGER (0..3,...),
	pDCCH-InterferenceImpact			INTEGER (0..4,...),
--EURECOM COMMENT, ADDED NEXT LINE 	iE-Extensions						ProtocolExtensionContainer { { RelativeNarrowbandTxPower-ExtIEs} } OPTIONAL,
	iE-Extensions               X2ap-IE-Extensions OPTIONAL,
	...
}

X2ap-RelativeNarrowbandTxPower-ExtIEs X2AP-PROTOCOL-EXTENSION ::= {
	...
}

X2ap-ReportAmountMDT ::= ENUMERATED{r1, r2, r4, r8, r16, r32, r64, rinfinity}

X2ap-ReportArea ::= ENUMERATED{
	ecgi,
	...
}

X2ap-ReportIntervalMDT ::= ENUMERATED {ms120, ms240, ms480, ms640, ms1024, ms2048, ms5120, ms10240, min1, min6, min12, min30, min60}

X2ap-ReportCharacteristics	::= BIT STRING (SIZE (32))

X2ap-ReportingTriggerMDT::= ENUMERATED{
	periodic,
	a2eventtriggered,
	...
}

X2ap-RNTP-Threshold ::= ENUMERATED {
	minusInfinity,
	minusEleven,
	minusTen,
	minusNine,
	minusEight,
	minusSeven,
	minusSix,
	minusFive,
	minusFour,
	minusThree,
	minusTwo,
	minusOne,
	zero,
	one,
	two,
	three,
	...
}

X2ap-RRC-Context ::= OCTET STRING

X2ap-RRCConnReestabIndicator ::= ENUMERATED {
	reconfigurationFailure, handoverFailure, otherFailure, ...
}
-- The values correspond to the values of ReestablishmentCause reported from the UE in the RRCConnectionReestablishmentRequest, as defined in TS 36.331 [9]

X2ap-RRCConnSetupIndicator::= ENUMERATED {
	rrcConnSetup,
	...
}

-- S

X2ap-S1TNLLoadIndicator ::= SEQUENCE {
	dLS1TNLLoadIndicator			X2ap-LoadIndicator,
	uLS1TNLLoadIndicator			X2ap-LoadIndicator,
--EURECOM COMMENT, ADDED NEXT LINE 	iE-Extensions					ProtocolExtensionContainer { { S1TNLLoadIndicator-ExtIEs} } OPTIONAL,
	iE-Extensions               X2ap-IE-Extensions OPTIONAL,
	...
}

X2ap-S1TNLLoadIndicator-ExtIEs X2AP-PROTOCOL-EXTENSION ::= {
	...
}




X2ap-ServedCells ::= SEQUENCE (SIZE (1.. x2ap-maxCellineNB)) OF ServedCellItem


ServedCellItem ::= SEQUENCE {
	servedCellInfo					X2ap-ServedCell-Information,
	neighbour-Info					X2ap-Neighbour-Information			OPTIONAL,
--EURECOM COMMENT, ADDED NEXT LINE 	iE-Extensions					ProtocolExtensionContainer { {ServedCell-ExtIEs} } OPTIONAL,
	iE-Extensions               X2ap-IE-Extensions OPTIONAL,
	...
}

X2ap-ServedCell-ExtIEs X2AP-PROTOCOL-EXTENSION ::= {
	...
}

X2ap-ServedCell-Information ::= SEQUENCE {
	pCI					X2ap-PCI,
	cellId				X2ap-ECGI,
	tAC					X2ap-TAC,
	broadcastPLMNs		X2ap-BroadcastPLMNs-Item,
	eUTRA-Mode-Info		X2ap-EUTRA-Mode-Info,
--EURECOM COMMENT, ADDED NEXT LINE 	iE-Extensions		ProtocolExtensionContainer { {X2ap-ServedCell-Information-ExtIEs} } OPTIONAL,
	iE-Extensions               X2ap-IE-Extensions OPTIONAL,
	...
}

X2ap-ServedCell-Information-ExtIEs X2AP-PROTOCOL-EXTENSION ::= {
--EURECOM	{ ID id-Number-of-Antennaports		CRITICALITY ignore	EXTENSION X2ap-Number-of-Antennaports			PRESENCE optional }|
--EURECOM	{ ID id-PRACH-Configuration			CRITICALITY ignore	EXTENSION X2ap-PRACH-Configuration				PRESENCE optional }|
--EURECOM	{ ID id-MBSFN-Subframe-Info			CRITICALITY ignore	EXTENSION X2ap-MBSFN-Subframe-Infolist			PRESENCE optional }|
--EURECOM	{ ID id-CSG-Id						CRITICALITY ignore	EXTENSION X2ap-CSG-Id							PRESENCE optional }|
--EURECOM	{ ID id-MBMS-Service-Area-List		CRITICALITY ignore	EXTENSION X2ap-MBMS-Service-Area-Identity-List	PRESENCE optional }|
--EURECOM	{ ID id-MultibandInfoList			CRITICALITY ignore	EXTENSION X2ap-MultibandInfoList					PRESENCE optional },
	...
}

X2ap-ShortMAC-I ::= BIT STRING (SIZE(16))

X2ap-SRVCCOperationPossible ::= ENUMERATED {
	possible,
	...
}

X2ap-SubframeAssignment ::= ENUMERATED { 
	sa0,
	sa1, 
	sa2,
	sa3,
	sa4,
	sa5,
	sa6,
	...
}

X2ap-SpecialSubframe-Info ::=    	SEQUENCE {
	specialSubframePatterns		X2ap-SpecialSubframePatterns,
	cyclicPrefixDL				X2ap-CyclicPrefixDL,
	cyclicPrefixUL				X2ap-CyclicPrefixUL,
--EURECOM COMMENT, ADDED NEXT LINE 	iE-Extensions				ProtocolExtensionContainer { { SpecialSubframe-Info-ExtIEs} } OPTIONAL,
	iE-Extensions               X2ap-IE-Extensions OPTIONAL,
	...
}

X2ap-SpecialSubframe-Info-ExtIEs X2AP-PROTOCOL-EXTENSION ::= {
	...
}


X2ap-SpecialSubframePatterns ::= ENUMERATED { 
	ssp0,
	ssp1, 
	ssp2,
	ssp3,
	ssp4,
	ssp5,
	ssp6,
	ssp7,
	ssp8,
	...,
	ssp9
}

X2ap-SubscriberProfileIDforRFP ::= INTEGER (1..256) 

X2ap-SubframeAllocation ::= CHOICE {
	oneframe						X2ap-Oneframe,
	fourframes						X2ap-Fourframes,
	...
}

-- T

X2ap-TAC ::= OCTET STRING (SIZE (2)) 

X2ap-TABasedMDT::= SEQUENCE {
	tAListforMDT		X2ap-TAListforMDT,
--EURECOM COMMENT, ADDED NEXT LINE 	iE-Extensions		ProtocolExtensionContainer { {TABasedMDT-ExtIEs} } OPTIONAL,
	iE-Extensions               X2ap-IE-Extensions OPTIONAL,
	...
}

X2ap-TABasedMDT-ExtIEs X2AP-PROTOCOL-EXTENSION ::= {
	...
}

X2ap-TAListforMDT ::= SEQUENCE (SIZE(1..x2ap-maxnoofTAforMDT)) OF X2ap-TAC

X2ap-TargetCellInUTRAN ::= OCTET STRING -- This IE is to be encoded according to the UTRAN Cell ID in the Last Visited UTRAN Cell Information IE in TS 25.413 [24]

X2ap-ThresholdEventA2 ::= SEQUENCE { 
	measurementThreshold		X2ap-MeasurementThresholdA2,
--EURECOM COMMENT, ADDED NEXT LINE 	iE-Extensions				ProtocolExtensionContainer { { ThresholdEventA2-ExtIEs} } OPTIONAL,
	iE-Extensions               X2ap-IE-Extensions OPTIONAL,
	...
}

X2ap-ThresholdEventA2-ExtIEs X2AP-PROTOCOL-EXTENSION ::= {
	...
}

X2ap-TargeteNBtoSource-eNBTransparentContainer	::= OCTET STRING

X2ap-Threshold-RSRP ::=  INTEGER(0..97)

X2ap-Threshold-RSRQ ::=  INTEGER(0..34)

X2ap-TimeToWait ::= ENUMERATED {
	v1s, 
	v2s, 
	v5s, 
	v10s, 
	v20s, 
	v60s, 
	...
}

X2ap-Time-UE-StayedInCell ::= INTEGER (0..4095)

X2ap-Time-UE-StayedInCell-EnhancedGranularity ::= INTEGER (0..40950)


X2ap-TraceActivation ::= SEQUENCE {
	eUTRANTraceID					X2ap-EUTRANTraceID,
	interfacesToTrace				X2ap-InterfacesToTrace,
traceDepth						X2ap-TraceDepth,
traceCollectionEntityIPAddress	X2ap-TraceCollectionEntityIPAddress,
--EURECOM COMMENT, ADDED NEXT LINE 	iE-Extensions					ProtocolExtensionContainer { {TraceActivation-ExtIEs} } OPTIONAL,
	iE-Extensions               X2ap-IE-Extensions OPTIONAL,
	...
}

X2ap-TraceActivation-ExtIEs X2AP-PROTOCOL-EXTENSION ::= {
--EURECOM	{ ID id-MDTConfiguration	CRITICALITY ignore	EXTENSION X2ap-MDT-Configuration		PRESENCE optional},
	...
}

X2ap-TraceCollectionEntityIPAddress ::= BIT STRING (SIZE(1..160, ...))

X2ap-TraceDepth 		::= ENUMERATED { 
	minimum,
	medium,
	maximum,
	minimumWithoutVendorSpecificExtension,
	mediumWithoutVendorSpecificExtension,
	maximumWithoutVendorSpecificExtension,
	...
}




X2ap-Transmission-Bandwidth ::= ENUMERATED {
		bw6,
	 	bw15,
		bw25,
	 	bw50,
		bw75,
		bw100,
		...
}

X2ap-TransportLayerAddress			::= BIT STRING (SIZE(1..160, ...))

X2ap-TypeOfError ::= ENUMERATED {
	not-understood,
	missing,
	...
}


-- U

X2ap-UE-HistoryInformation ::= SEQUENCE (SIZE(1..x2ap-maxnoofCells)) OF X2ap-LastVisitedCell-Item


X2ap-UE-S1AP-ID					::= INTEGER (0.. 4294967295)

X2ap-UE-X2AP-ID					::= INTEGER (0..4095)

X2ap-UEAggregateMaximumBitRate ::= SEQUENCE {
	uEaggregateMaximumBitRateDownlink	X2ap-BitRate,
	uEaggregateMaximumBitRateUplink		X2ap-BitRate,
--EURECOM COMMENT, ADDED NEXT LINE 	iE-Extensions						ProtocolExtensionContainer { {UEAggregate-MaximumBitrate-ExtIEs} } OPTIONAL,
	iE-Extensions               X2ap-IE-Extensions OPTIONAL,
	...
}

X2ap-UEAggregate-MaximumBitrate-ExtIEs X2AP-PROTOCOL-EXTENSION ::= {
	...
}

X2ap-UESecurityCapabilities ::= SEQUENCE {
	encryptionAlgorithms				X2ap-EncryptionAlgorithms,
	integrityProtectionAlgorithms		X2ap-IntegrityProtectionAlgorithms,
--EURECOM COMMENT, ADDED NEXT LINE 	iE-Extensions						ProtocolExtensionContainer { { UESecurityCapabilities-ExtIEs} }		OPTIONAL,
	iE-Extensions               X2ap-IE-Extensions OPTIONAL,
...
}

X2ap-UESecurityCapabilities-ExtIEs X2AP-PROTOCOL-EXTENSION ::= {
	...
}

X2ap-UL-GBR-PRB-usage::= INTEGER (0..100)

X2ap-UL-non-GBR-PRB-usage::= INTEGER (0..100)

X2ap-UL-Total-PRB-usage::= INTEGER (0..100)

X2ap-UL-InterferenceOverloadIndication ::= SEQUENCE (SIZE(1..x2ap-maxnoofPRBs)) OF X2ap-UL-InterferenceOverloadIndication-Item

X2ap-UL-InterferenceOverloadIndication-Item ::= ENUMERATED {
	high-interference,
	medium-interference,
	low-interference,
	...
}

X2ap-UL-HighInterferenceIndicationInfo ::= SEQUENCE (SIZE(1..x2ap-maxCellineNB)) OF X2ap-UL-HighInterferenceIndicationInfo-Item

X2ap-UL-HighInterferenceIndicationInfo-Item ::= SEQUENCE {
	target-Cell-ID					X2ap-ECGI,
	ul-interferenceindication		X2ap-UL-HighInterferenceIndication,
--EURECOM COMMENT, ADDED NEXT LINE 	iE-Extensions					ProtocolExtensionContainer { { UL-HighInterferenceIndicationInfo-Item-ExtIEs} } OPTIONAL,
	iE-Extensions               X2ap-IE-Extensions OPTIONAL,
	...
}

X2ap-UL-HighInterferenceIndicationInfo-Item-ExtIEs X2AP-PROTOCOL-EXTENSION ::= {
	...
}

X2ap-UL-HighInterferenceIndication ::= BIT STRING (SIZE(1..110, ...))

X2ap-UE-RLF-Report-Container::= OCTET STRING
-- This IE is a transparent container and shall be encoded as the rlfReport field contained in the UEInformationResponse message as defined in TS 36.331 [9]

X2ap-UsableABSInformation ::= CHOICE {
	fdd					X2ap-UsableABSInformationFDD,
	tdd					X2ap-UsableABSInformationTDD,
	...
}

X2ap-UsableABSInformationFDD ::= SEQUENCE {
	usable-abs-pattern-info				BIT STRING (SIZE(40)),
--EURECOM COMMENT, ADDED NEXT LINE 	iE-Extensions						ProtocolExtensionContainer { { UsableABSInformationFDD-ExtIEs} } OPTIONAL,
	iE-Extensions               X2ap-IE-Extensions OPTIONAL,
	...
}

X2ap-UsableABSInformationFDD-ExtIEs X2AP-PROTOCOL-EXTENSION ::= {
	...
}

X2ap-UsableABSInformationTDD ::= SEQUENCE {
	usaable-abs-pattern-info			BIT STRING (SIZE(1..70, ...)),
--EURECOM COMMENT, ADDED NEXT LINE 	iE-Extensions						ProtocolExtensionContainer { { UsableABSInformationTDD-ExtIEs} } OPTIONAL,
	iE-Extensions               X2ap-IE-Extensions OPTIONAL,
	...
}

X2ap-UsableABSInformationTDD-ExtIEs X2AP-PROTOCOL-EXTENSION ::= {
	...
}

-- V
-- W
-- X
-- Y
-- Z

END
